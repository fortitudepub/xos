module xos {
    yang-version 1;
    namespace "urn:com:xsdn:xos:params:xml:ns:yang:xos";
    prefix "xos";

    import ietf-inet-types {prefix inet; revision-date "2010-09-24";}
    import ietf-yang-types {prefix yang; revision-date "2010-09-24";}
    import opendaylight-flow-types {prefix flow;revision-date "2013-10-26";}
    import opendaylight-group-types {prefix group;revision-date "2013-10-18";}

    revision "2015-08-20" {
        description "Initial revision of xos model";
    }

    /* NOTE:
       We will add some asiainfo related variables here, it will be abbreviated to ai. 

       NOTE_ZDY:
       I suggest use ai- prefix for data tree node of list type as naming convention to solve the following
       problem:

       For example we have the following data definition:

       list tests {
       uses test;
       }

       YANG-TOOLS generated Tests class to abstract the list member, however, there is also a Test class which
       means the test type, this will cause confusing for us when we programming or reading other code.

       The list name is also suggested to does not keep the postfix 's', otherwise the generated list
       member class will also have the 's' postfix, which seems no reasonable as a singular.

       So the desired definition should be
       list ai-test {
       uses test;
       }

       TODO:
       We may support a simple LACP to form MLAG for the attached host between the intermediate L2SW
       link may not down even OFSW down.
    */

    typedef flow-id {
        description "MD-SAL identifier of openflow flow. ";
        type inet:uri;
    }

    grouping virtual-gateway {
        leaf virtual-gateway-ip {
            type inet:ipv4-address;
            description "IPv4 address of the virtual gateway interface";
        }

        /* The mac should moved to the SDN switch container as most L3 HW switch use a single router mac,
           add a virtual-gatway-mac per subnet is duplicate.
        leaf virtual-gateway-mac {
            type yang:mac-address;
            description "MAC address of the virtual gateway interface, will be used for ARP proxy and routing
                         identification.";
        }
        */
    }

    /* Define the host connected directly or indirectly to the SDN switch, the IP address should be
       configured by user.
    */
    grouping managed-host {
        leaf managed-host-ip {
            type inet:ipv4-address;
            description "IPv4 address of the virtual interface";
        }

        leaf managed-host-mac {
            type yang:mac-address;
            config false; /* This mac address is learned by using arp probe mechanism. */
            description "MAC address of the virtual interface, will be used for ARP proxy and routing
                         identification.";
        }

        leaf managed-host-ingress {
            type int16;
            config false; /* This ingress is learned by packetIn. */
            description "IN_PORT of the virtual interface, will be used for l2 flow forwarding.";
        }
    }

    /* The subnet is used to isolate learning/bridging domain, by default host in different subnet can not
       communicate with each other. */
    grouping managed-subnet {
        /* Use id as key does not provide any isolation for the case virtual-gateway and host ip overlaps,
           we should put some contraint here. */
        leaf subnet-id {
            type int16;
            description "Id of the managed subnet.";
        }

        container virtual-gateway {
            uses virtual-gateway;
            description "Virtual gateway of this subnet.";
        }
        
        list subnet-host {
            uses managed-host;
            key "managed-host-ip";
            description "Host on this subnet.";
        }
    }

    grouping sdn-switch {
        description "Abstract representation of a SDN switch.";

        leaf dpid {
            type string;
            description "SDN switch dpid in string format, this is provided by user through api.";
        }

        leaf virtual-gateway-mac {
            type yang:mac-address;
            description "MAC address of the virtual gateway, will be used to proxy gateway ARP request for subnet
                        and for routing packet identification.";
        }

        leaf quagga-interface-ip {
            type inet:ipv4-address;
            description "The IP of the ospf interface of the host which is connected to SDN switch and runs quagga, we
                         spoof its mac and port, the mac will be used as ethernet source mac of the default route.";
        }

        leaf edge-router-interface-ip {
            type inet:ipv4-address;
            description "The IP of the interface which edge router enabled ospf to connect quagga, we spoof its mac
                         and port, and use it as default route to forward dns-reply to the edge router.";
        }

        list user-flow {
            key "id";

            leaf id {
                type flow:flow-id;
            }

            uses flow:flow;
        }

        list user-group {
            key "id";

            leaf id {
                type group:group-id;
            }

            uses group:group;
        }

        list app-flow {
            key "id";

            leaf id {
                type flow-id;
            }

            uses flow:flow;

            config false; /* App flow is generated by our application, and should be read only for end user. */
        }
    }

    container xos {
        container ai-active-passive-switchset {
            container dns {
                leaf anycast-dns-ip {
                    type inet:ipv4-address;
                    description "The ipv4 anycast address this switchset will serve.";
                }
            }

            /* The active passive switch acts as an cluster, so the subnet is managed by the cluster instead
               of the individual switch. */
            list ai-managed-subnet {
                uses managed-subnet;
                key "subnet-id";
                description "Managed subnets by this cluster.";
            }
                
            container east {
                container east-switch {
                    uses sdn-switch;
                    description "SDN switch deployed on the west of the topology.";

                    must "dpid != ''" {
                        error-message "dpid must not be empty.";
                    }
                }

                leaf active {
                    type boolean;
                    description "active-passive status, true means active.";
                    config false;
                }
            }

            container west {
                container west-switch {
                    uses sdn-switch;
                    description "SDN switch deployed on the east of the topology.";

                    must "dpid != ''" {
                        error-message "dpid must not be empty.";
                    }
                }
                
                leaf active {
                    type boolean;
                    description "active-passive status, true means active.";
                    config false;
                }
            }
        }
    }
    
    /* TODO: add our persistent data model here.*/

    rpc force-failover-switch {
        input {
            leaf nop {
                type string;
            }
        }
        output {
        }
    }
}
