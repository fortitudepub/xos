module xos-main {
    yang-version 1;
    namespace "urn:com:xsdn:xos:params:xml:ns:yang:xos:main";
    prefix "xos-main";

    import config { prefix config; revision-date 2013-04-05; }
    import opendaylight-md-sal-binding { prefix md-sal-binding; revision-date 2013-10-28;}
    import opendaylight-entity-ownership-service { prefix entity-ownership-service; }
    import opendaylight-sal-binding-broker-impl { prefix sal-broker; revision-date 2013-10-28;}

    description
        "Service definition for xos project";

    revision "2015-08-20" {
        description
            "Initial revision";
    }

    /* Rename this to xos-main to solve conflict with xos.yang data model. */
    identity xos-main {
        base config:module-type;
        config:java-name-prefix Xos;
    }

    augment "/config:modules/config:module/config:configuration" {
        case xos-main {
            when "/config:modules/config:module/config:type = 'xos-main'";

            container data-broker {
                uses config:service-ref {
                    refine type {
                        mandatory true;
                        config:required-identity md-sal-binding:binding-async-data-broker;
                    }
                }
            }

            container notification-service {
                 uses config:service-ref {
                      refine type {
                        mandatory true;
                        /* use new design should switch to this notification service.
                           config:required-identity md-sal-binding:binding-notification-service; */
                        config:required-identity sal-broker:binding-new-notification-service;
                      }
                 }
            }

            container rpc-registry {
                 uses config:service-ref {
                        refine type {
                         mandatory true;
                         config:required-identity md-sal-binding:binding-rpc-registry;
                        }
                 }
            }

            container binding-aware-broker {
                uses config:service-ref {
                    refine type {
                        mandatory true;
                        config:required-identity md-sal-binding:binding-broker-osgi-registry;
                    }
                }
            }

            container entity-ownership-service {
                uses config:service-ref {
                    refine type {
                        mandatory true;
                        config:required-identity entity-ownership-service:entity-ownership-service;
                    }
                }
            }
        }
    }
}
